module firstYang {
    namespace "http://councharles.com/firstYang";
    prefix "fyy";
    typedef vlan-id { type uint16 {range "1..4094";}}

    container switch {
    leaf Hostname { type string;}
    list interface { 
        key name;
        leaf name {type string{ pattern ".*Ethernet0/[0-9]+";} 
        }
        leaf description {type string {length "4..50";}
        }
        leaf speed { type uint32;
                      units "Mbps";
                      config false;  
        }
        leaf mode { type enumeration {enum access; enum trunk;}
        }

        choice access-or-trunk { case access {leaf access-vlan {type vlan-id;} when "mode='access'";}
                                 case trunk {leaf-list trunked-vlans {type vlan-id;} when "mode='trunk'";}
        }



        }
    }
}
